module k8sfilter {
  yang-version 1.1;
  namespace "http://polycube.network/nat";
  prefix "k8sfilter";

  import polycube-base { prefix "basemodel"; }

  organization "Polycube open source project";
  description "YANG data model for the Polycube traffic filter for Kubernetes";

  basemodel:service-description "Kubernetes Traffic Filtering Service";
  basemodel:service-version "2.0";
  basemodel:service-name "k8sfilter";
  basemodel:service-min-kernel-version "4.14.0";

  uses "basemodel:base-yang-module" {
    augment ports {
      leaf type {
        type enumeration {
          enum EXTERNAL { description "Connected to NIC"; }
          enum INTERNAL { description "Connected to LBRP"; }
        }
        mandatory true;
        config false;
        description "...";
      }
    }
  }

  leaf nodeport-range {
    type string;
    description "Port range used for NodePort services";
    default "30000-32767";
    basemodel:cli-example "30000-32767";
  }
}
