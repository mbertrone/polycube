module k8switch {
  yang-version 1.1;
  namespace "http://polycube.network/k8switch";
  prefix "k8switch";

  import polycube-base { prefix "basemodel"; }
  import ietf-inet-types { prefix "inet"; }

  organization "Polycube open source project";
  description "YANG data model for the Polycube HyperSwitch for Kubernetes";

  basemodel:service-description "Kubernetes HyperSwitch Service";
  basemodel:service-version "2.0.0";
  basemodel:service-name "k8switch";
  basemodel:service-min-kernel-version "4.14.0";

  uses "basemodel:base-yang-module" {
    augment ports {
      leaf type {
        type enumeration {
          enum DEFAULT { description "Port connected to the clients and linux stack"; }
          enum NODEPORT { description "Port to provide NodePort services"; }
        }
        mandatory false;
        default DEFAULT;
        description "Type of the LB port (e.g. NODEPORT or DEFAULT)";
      }
    }
  }

  leaf cluster-ip-subnet {
    type inet:ipv4-prefix;
    description "Range of VIPs where clusterIP services are exposed";
    basemodel:cli-example "10.96.0.0/12";
    mandatory true;
  }

  leaf client-subnet {
    type inet:ipv4-prefix;
    description "Range of IPs of pods in this node";
    basemodel:cli-example "192.168.1.0/24";
    mandatory true;
  }

  leaf virtual-client-subnet {
    type inet:ipv4-prefix;
    description "Range where client's IPs are mapped into";
    basemodel:cli-example "10.10.1.0/24";
    mandatory true;
  }

  list service {
    key "vip vport proto";
    description "Services (i.e., virtual ip:protocol:port) exported to the client";
    leaf name {
      type string;
      description "Service name related to the backend server of the pool is connected to";
      basemodel:cli-example "Service-nigx";
    }

    leaf vip {
      type inet:ipv4-address;
      description "Virtual IP (vip) of the service where clients connect to";
      basemodel:cli-example "130.192.100.12";
    }

    leaf vport {
      type inet:port-number;
      description "Port of the virtual server where clients connect to (this value is ignored in case of ICMP)";
      basemodel:cli-example "80";
    }

    leaf proto {
      type enumeration {
          enum TCP;
          enum UDP;
      }
      mandatory true;
      description "Upper-layer protocol associated with a loadbalancing service instance.";
    }

    list backend {
      key "ip port";
      description "Pool of backend servers that actually serve requests";
      leaf name {
        type string;
        description "name";
        basemodel:cli-example "backend1";
      }

      leaf ip {
        type inet:ipv4-address;
        description "IP address of the backend server of the pool";
        basemodel:cli-example "10.244.1.23";
      }

      leaf port {
        type inet:port-number;
        description "Port where the server listen to (this value is ignored in case of ICMP)";
        basemodel:cli-example "80";
      }

      leaf weight {
        type uint16;
        description "Weight of the backend in the pool";
        basemodel:cli-example "1";
      }
    }
  }

  list fwd-table {
    key "address";
    description "Entry associated with the forwarding table";
    leaf address {
      type inet:ip-prefix;
      mandatory true;
      description "Destination IP address";
      basemodel:cli-example "123.13.34.0";
    }

    leaf mac {
      type string;
      mandatory true;
      description "Destination MAC address";
      basemodel:cli-example "C5:13:2D:36:27:9B";
    }

    leaf port {
      type string;
      mandatory true;
      description "Port where this entry is present";
      basemodel:cli-example "port1";
    }
  }
}
