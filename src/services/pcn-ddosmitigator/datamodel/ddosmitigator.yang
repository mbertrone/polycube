module ddosmitigator {
  yang-version 1.1;
  namespace "http://polycube.network/ddosmitigator";
  prefix "ddosmitigator";

  import polycube-base { prefix "basemodel"; }

  organization "Polycube open source project";
  description "YANG data model for the Polycube DDoS Mitigator service";

  basemodel:service-description "DDoS Mitigator Service";
  basemodel:service-version "2.0";
  basemodel:service-name "ddosmitigator";
  basemodel:service-min-kernel-version "4.14.0";

  uses "basemodel:base-yang-module";

  container stats {
    description "Statistics on dropped packets";
    config false;

    leaf pps {
      type uint64;
      config false;
      description "Dropped Packets/s";
    }

    leaf pkts {
      type uint64;
      config false;
      description "Total Dropped Packets";
    }
  }

  leaf active-port {
    type string;
    description "Port where the traffic is received";
  }

  leaf redirect-port {
    type string;
    description "If set, this will be the port used to redirect traffic (instead of PASS it to STACK)";
  }

  list blacklist-src {
      key "ip";
      description "Blacklisted source IP addresses";

      leaf ip {
        type string;
        description "Source IP Address";
        basemodel:cli-example "10.0.0.1";
      }

      leaf drop-pkts {
        type uint64;
        config false;
        description "Dropped Packets";
      }
  }

  list blacklist-dst {
      key "ip";
      description "Blacklisted destination IP addresses";

      leaf ip {
        type string;
        description "Destination IP Address";
        basemodel:cli-example "10.0.0.2";
      }

      leaf drop-pkts {
        type uint64;
        config false;
        description "Dropped Packets";
      }
  }
}
