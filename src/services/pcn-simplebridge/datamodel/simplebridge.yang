module simplebridge {
  yang-version 1.1;
  namespace "http://polycube.network/simplebridge";
  prefix "simplebridge";

  import polycube-base { prefix "basemodel"; }
  import ietf-yang-types { prefix "yang"; }

  organization "Polycube open source project";
  description "YANG data model for the Polycube simple L2 bridge";

  basemodel:service-description "Simple L2 Bridge Service";
  basemodel:service-version "1.0.0";
  basemodel:service-name "simplebridge";
  basemodel:service-min-kernel-version "4.11.0";

  uses "basemodel:base-yang-module" {
    augment ports {
      leaf mac {
        type yang:mac-address;
        description "MAC address of the port";
        config true;
        basemodel:init-only-config;
        basemodel:cli-example "C5:13:2D:36:27:9B";
      }
    }
  }

  container fdb {
    leaf aging-time {
      type uint32;
      units seconds;
      default 300;
      description "Aging time of the filtering database (in seconds)";
      basemodel:cli-example "300";
    }

    list entry {
      key "address";
      description "Entry associated with the filtering database";
      leaf address {
        type yang:mac-address;
        mandatory true;
        description "Address of the filtering database entry";
        basemodel:cli-example "C5:13:2D:36:27:9B";
      }

      leaf port {
        type string;
        mandatory true;
        description "Output port name";
        basemodel:cli-example "port2";
      }

      leaf age {
        type uint32;
        units seconds;
        description "Age of the current filtering database entry";
        config false;
      }
    }

    action flush {
      description "Flushes the filtering database of the bridge";
      output {
        leaf flushed {
          type boolean;
          description "Returns true if the Filtering database has been flushed. False otherwise";
          mandatory true;
        }
      }
    }
  }
}
