module router {
  yang-version 1.1;
  namespace "http://polycube.network/router";
  prefix "router";

  import polycube-base { prefix "basemodel"; }

  import ietf-inet-types { prefix "inet"; }
  import ietf-yang-types { prefix "yang";  }

  organization "Polycube open source project";
  description "YANG data model for the Polycube Router service";

  basemodel:service-description "Router Service";
  basemodel:service-version "2.0";
  basemodel:service-name "router";
  basemodel:service-min-kernel-version "4.15.0";

  uses "basemodel:base-yang-module" {
     augment ports {
       leaf ip {
        type inet:ipv4-address;
        mandatory true;
        description "IP address of the port";
        basemodel:cli-example "207.46.130.1";
      }

      leaf netmask {
        type inet:ipv4-address;
        mandatory true;
        description "Netmask of the port";
        basemodel:cli-example "255.255.255.0";
      }

      list secondaryip {
        description "Secondary IP address for the port";
        key "ip netmask";
        leaf ip {
          type inet:ipv4-address;
          mandatory true;
          description "Seconadary IP address of the port";
          basemodel:cli-example "207.46.131.1";
        }

        leaf netmask {
          type inet:ipv4-address;
          mandatory true;
          description "Secondary netmask of the port";
          basemodel:cli-example "255.255.255.0";
        }
      }

      leaf mac {
        type yang:mac-address;
        description "MAC address of the port";
        basemodel:cli-example "B3:23:45:F5:3A";
      }
    }
  }

  list route {
    key "network netmask nexthop";
    description "Entry associated with the routing table";
    leaf network {
      type inet:ipv4-address;
      mandatory true;
      description "Destination network IP";
      basemodel:cli-example "123.13.34.0";
    }

    leaf netmask {
      type inet:ipv4-address;
      mandatory true;
      description "Destination network netmask";
      basemodel:cli-example "255.255.255.0";
    }

    leaf nexthop {
      type inet:ipv4-address;
      mandatory true;
      description "Next hop; if destination is local will be shown 'local' instead of the ip address";
      basemodel:cli-example "123.14.23.3";
    }

    leaf interface {
      type string;
      config true;
      basemodel:init-only-config;
      description "Outgoing interface";
      basemodel:cli-example "port2";
    }

    leaf pathcost {
      type int32;
      default 1;
      description "Cost of this route";
      basemodel:cli-example "10";
    }
  }

  list arp-entry {
    key "address";
    description "Entry associated with the ARP table";
    leaf address {
      type inet:ip-prefix;
      mandatory true;
      description "Destination IP address";
      basemodel:cli-example "123.13.34.0";
    }

    leaf mac {
      type string;
      mandatory true;
      description "Destination MAC address";
      basemodel:cli-example "C5:13:2D:36:27:9B";
    }

    leaf interface {
      type string;
      mandatory true;
      description "Outgoing interface";
      basemodel:cli-example "port2";
    }
  }
}
